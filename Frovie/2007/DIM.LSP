(defun c:xy()
(setq a (getpoint "Pick a point:"))
(setq s (strcat (rtos (car a) 2 2) " / " (rtos (cadr a) 2 2)))
(command "LEADER" a pause pause s "")
)
(defun c:xdim()
(setq a (getpoint "Pick a point:"))
(setq s (strcat (rtos (car a) 2 2)))
(command "LEADER" a pause pause s "")
)
(defun c:ydim()
(setq a (getpoint "Pick a point:"))
(setq s (strcat (rtos (cadr a) 2 2)))
(command "DIM" "VER" a pause pause s "EXIT")
)
(defun c:xxdim()
(setq a (getpoint "Pick a point:"))
(setq s (strcat (rtos (car a) 2 2)))
(command "DIM" "HOR" a pause pause s "EXIT")
)
